FME workspace ACTUAL VERSION - Getting Areas.fmw

Parameters:
- SourceDataset_OSM = F:\HDD\Downloads\map (3).osm   # Source OpenStreetMap File(s)
- SourceDataset_GEOJSON = C:\Users\Leon\OneDrive - Lancaster University\buildings.geojson   # Source GeoJSON File or URL
- DestDataset_CITYGML = $(FME_MF_DIR)buildings_attributes.gml   # Destination CityGML Document
- DestDataset_XLSXW = buildingsOSW.xlsx   # Destination Microsoft Excel File
- SourceDataset_XLSXR_5 = C:\Users\Leon\Documents\Python\ENGR PROJECT\Height\building_heights_new.xlsx   # Source Microsoft Excel File(s)
- DestDataset_CESIUM3DTILES = C:\Users\Leon\Documents\FME\Workspaces\Cesium   # Destination Cesium 3D Tiles Folder
- SourceDataset_XLSXR_7 = C:\Users\Leon\Documents\Python\ENGR PROJECT\Height\building_heights_new.xlsx   # Source Microsoft Excel File(s)
- SourceDataset_XLSXR = C:\Users\Leon\Documents\Python\ENGR PROJECT\Height\building_heights_april_0804.xlsx   # Source Microsoft Excel File(s)
- DestDataset_XLSXW_5 = OSM_areas.xlsx   # Destination Microsoft Excel File
- DestDataset_XLSXW_4 = C:\Users\Leon\Documents\Python\ENGR PROJECT\Height\OSM_areas.xlsx   # Destination Microsoft Excel File

Readers:
- OSM_1: OSM from $(SourceDataset_OSM)
- GEOJSON_1: GEOJSON from $(SourceDataset_GEOJSON)
- XLSXR_1: XLSXR from $(SourceDataset_XLSXR_5)
- XLSXR_2: XLSXR from $(SourceDataset_XLSXR_7)
- XLSXR_3: XLSXR from $(SourceDataset_XLSXR)

Writers:
- CITYGML_1: CITYGML to $(DestDataset_CITYGML)
- XLSXW_1: XLSXW to $(DestDataset_XLSXW)
- CESIUM3DTILES_1: CESIUM3DTILES to $(DestDataset_CESIUM3DTILES)
- XLSXW_2: XLSXW to $(DestDataset_XLSXW_5)
- XLSXW_3: XLSXW to $(DestDataset_XLSXW_4)

Note: OSM Building data loaded
buildings (reader GEOJSON_1)
    attributes: osm_id int, addr:housenumber string, building string, addr:housename string, name string, amenity string, access string, covered string, shop string, power string, operator string, sport string, leisure string, man_made string, residential string, addr:place string, addr:city string, addr:postcode string, bicycle_parking string, building:levels string, wheelchair string, addr:street string, healthcare string, description string, old_name string, website string, fhrs:id string, building:flats string, alt_name string, location string,
      recycling_type string
    -> FeatureMerger [REQUESTOR]
Note: OSM-linked Planon Floor/Height Data loaded
Sheet1 (reader XLSXR_3)
    attributes: A number(4,0), Unnamed: 0_x number(4,0), Property Name char(48), Property code_x number(2,0), Floor number(3,0), Space number number(4,0), Space Name number(4,0), Property code_y char(6), osm_id number(10,0), addr:housenumber number(4,0), building_type char(13), addr:housename char(41), name_x char(43), amenity char(8), Height number(3,0), year_of_build number(5,0), Total_GIA number(20,13)
    -> FeatureMerger [SUPPLIER]
Note: FeatureMerger [FeatureMerger] / Transformer: / Group By Mode: Process At End (Blocking) / Suppliers First: No / Join On: RequestorSupplierComparison Mode@Value(osm_id)@Value(osm_id)AutomaticMerge Parameters: / Feature Merge Type: Attributes Only / Reject Null and Missing Keys: No / Attribute Accumulation: / Accumulation Mode: Merge Supplier / Conflict Resolution: Use Requestor / Ignore Nulls: No
Note: FeatureMerger - merge buildings with floor data on OSM id (equivalent to pandas merge or SQL join)
FeatureMerger
    ATTR_ACCUM_MODE = Merge Supplier
    ATTR_CONFLICT_RES = Use Requestor
    IGNORE_NULLS = No
    JOIN_KEYS = @Value(osm_id) @Value(osm_id) AUTO
    MERGE_TYPE = Attributes Only
    PROCESS_DUPS = NO
    REJECT_NULL_MISSING_KEYS = No
    SUPPLIERS_FIRST = No
    MERGED -> GeographicAreaCalculator
Note: Calculates area of each matched building polygon and attaches it as attribute 'area2'
GeographicAreaCalculator
    AREA_ATTR = _area2
    AreaMult = 1
    -> Sheet1 (writer XLSXW_3)
Note: Writes all attributes (with area2) now to an Excel sheet
Sheet1 (writer XLSXW_3)
    attributes: osm_id number(20), addr:housenumber string(20), building string(20), addr:housename string(20), name string(20), amenity string(20), access string(20), covered string(20), shop string(20), power string(20), operator string(20), sport string(20), leisure string(20), man_made string(20), residential string(20), addr:place string(20), addr:city string(20), addr:postcode string(20), bicycle_parking string(20), building:levels string(20), wheelchair string(20), addr:street string(20), healthcare string(20), description string(20), old_name string(20), website string(20), fhrs:id string(20), building:flats string(20), alt_name string(20), location string(20),
      recycling_type string(20), A number(4), Unnamed: 0_x number(4), Property Name string(48), Property code_x number(2), Floor number(3), Space number number(4), Space Name number(4), Property code_y string(6), building_type string(13), name_x string(43), Height number(3), year_of_build number(5), Total_GIA number(20), _area2 auto(20)
Extruder
    DIRECTION = Vertical
    DISTANCE = FME_CONDITIONAL:DEFAULT_VALUE'1'BOOL_OP;OR;COMPOSITE_TEST;1;TEST @Value(osm_id) = @Value(osm_id)'@Value(Height)'FME_NUM_CONDITIONS2___
    EXTRUDED -> NullAttributeMapper
NullAttributeMapper
    ATTRCHOICE = Selected Attributes
    ATTRLIST = Height
    NEW_VALUE = 15
    NULL_TREATMENT = New Value
    SOURCE_ATTR_VAL = Null
    -> FeatureWriter [Output]
    -> NewFeatureType (writer CITYGML_1)
    -> buildings (writer CESIUM3DTILES_1)
buildings (writer CESIUM3DTILES_1)
FeatureWriter
    CITYGML_ADD_NAMESPACE_PREFIX_TO_FEATURE_TYPES = No
    CITYGML_ADE = None
    CITYGML_CITYGML_VALIDATION = No
    CITYGML_COORDINATE_SYSTEM_GRANULARITY = DATASET
    CITYGML_DESTINATION_DATASETTYPE_VALIDATION = Yes
    CITYGML_DOCUMENT_ENCODING = utf-8
    CITYGML_INDENT_SIZE = 1
    CITYGML_PRETTY_PRINT = No
    CITYGML_REMOVE_AUTO_GENERATED_IDS_WHEN_POSSIBLE = Yes
    CITYGML_REPLACE_TABS_WITH_SPACES = No
    CITYGML_RESTRICT_CURVES_TO_POLYLINES = Yes
    CITYGML_TEXTURE_OUTPUT_FORMAT = NONE
    CITYGML_THEME_NAME = FMETheme
    CITYGML_USE_CITYGML_SCHEMA_FILES = Yes
    CITYGML_USE_CORE_NAMESPACE_PREFIX = Yes
    CITYGML_USE_XLINK_HREF_GEOMETRY_TRAITS = Yes
    CITYGML_VERSION = 2.0
    DATASET = $(FME_MF_DIR_ENCODED)buildingsFinal.gml
    DATASET_ATTR = _dataset
    FEATURE_TYPE_LIST_ATTR = _feature_type
    FORMAT = CITYGML
    TOTAL_FEATURES_WRITTEN_ATTR = _total_features_written
NewFeatureType (writer CITYGML_1)
