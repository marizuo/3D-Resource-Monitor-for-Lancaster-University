FME workspace ACTUAL VERSION - 3d Tiles.fmw

Parameters:
- SourceDataset_OSM = F:\HDD\Downloads\map (3).osm   # Source OpenStreetMap File(s)
- SourceDataset_GEOJSON = C:\Users\Leon\OneDrive - Lancaster University\buildings.geojson   # Source GeoJSON File or URL
- DestDataset_CITYGML = $(FME_MF_DIR)buildings_attributes.gml   # Destination CityGML Document
- DestDataset_XLSXW = buildingsOSW.xlsx   # Destination Microsoft Excel File
- SourceDataset_XLSXR_5 = C:\Users\Leon\Documents\Python\ENGR PROJECT\Height\building_heights_new.xlsx   # Source Microsoft Excel File(s)
- DestDataset_CESIUM3DTILES = C:\Users\Leon\Documents\FME\Workspaces\Cesium   # Destination Cesium 3D Tiles Folder
- SourceDataset_XLSXR_7 = C:\Users\Leon\Documents\Python\ENGR PROJECT\Height\building_heights_new.xlsx   # Source Microsoft Excel File(s)
- SourceDataset_XLSXR = C:\Users\Leon\Documents\Python\ENGR PROJECT\Height\building_heights_april_0804.xlsx   # Source Microsoft Excel File(s)
- DestDataset_XLSXW_5 = OSM_areas.xlsx   # Destination Microsoft Excel File
- DestDataset_CESIUM3DTILES_3 = C:\Users\Leon\Documents\FME\Workspaces\lucampus   # Destination Cesium 3D Tiles Folder
- SourceDataset_XLSXR_6 = C:\Users\Leon\Documents\Python\ENGR PROJECT\Height\building_heights_april_0804.xlsx   # Source Microsoft Excel File(s)

Readers:
- OSM_1: OSM from $(SourceDataset_OSM)
- GEOJSON_1: GEOJSON from $(SourceDataset_GEOJSON)
- XLSXR_1: XLSXR from $(SourceDataset_XLSXR_5)
- XLSXR_2: XLSXR from $(SourceDataset_XLSXR_7)
- XLSXR_3: XLSXR from $(SourceDataset_XLSXR)
- XLSXR_4: XLSXR from $(SourceDataset_XLSXR_6)

Writers:
- CITYGML_1: CITYGML to $(DestDataset_CITYGML)
- XLSXW_1: XLSXW to $(DestDataset_XLSXW)
- CESIUM3DTILES_1: CESIUM3DTILES to $(DestDataset_CESIUM3DTILES)
- XLSXW_2: XLSXW to $(DestDataset_XLSXW_5)
- CESIUM3DTILES_2: CESIUM3DTILES to $(DestDataset_CESIUM3DTILES_3)

Note: OSM Building data loaded
buildings (reader GEOJSON_1)
    attributes: osm_id int, addr:housenumber string, building string, addr:housename string, name string, amenity string, access string, covered string, shop string, power string, operator string, sport string, leisure string, man_made string, residential string, addr:place string, addr:city string, addr:postcode string, bicycle_parking string, building:levels string, wheelchair string, addr:street string, healthcare string, description string, old_name string, website string, fhrs:id string, building:flats string, alt_name string, location string,
      recycling_type string
    -> FeatureMerger [REQUESTOR]
Note: OSM-linked Planon Height/YoB/GIA data loaded
Sheet1 (reader XLSXR_3)
    attributes: A number(4,0), Unnamed: 0_x number(4,0), Property Name char(48), Property code_x number(2,0), Floor number(3,0), Space number number(4,0), Space Name number(4,0), Property code_y char(6), osm_id number(10,0), addr:housenumber number(4,0), building_type char(13), addr:housename char(41), name_x char(43), amenity char(8), Height number(3,0), year_of_build number(5,0), Total_GIA number(20,13)
    -> FeatureMerger [SUPPLIER]
Note: FeatureMerger [FeatureMerger] / Transformer: / Group By Mode: Process At End (Blocking) / Suppliers First: No / Join On: RequestorSupplierComparison Mode@Value(osm_id)@Value(osm_id)AutomaticMerge Parameters: / Feature Merge Type: Attributes Only / Reject Null and Missing Keys: No / Attribute Accumulation: / Accumulation Mode: Merge Supplier / Conflict Resolution: Use Requestor / Ignore Nulls: No
Note: FeatureMerger - merge buildings with floor data on OSM id (equivalent to pandas merge or SQL join)
Note: Only take merged values - (inner join)
FeatureMerger
    ATTR_ACCUM_MODE = Merge Supplier
    ATTR_CONFLICT_RES = Use Requestor
    IGNORE_NULLS = No
    JOIN_KEYS = @Value(osm_id) @Value(osm_id) AUTO
    MERGE_TYPE = Attributes Only
    PROCESS_DUPS = NO
    REJECT_NULL_MISSING_KEYS = No
    SUPPLIERS_FIRST = No
    MERGED -> Extruder
Note: Extrude the 2D outline by their height attribute
Extruder
    DIRECTION = Vertical
    DISTANCE = FME_CONDITIONAL:DEFAULT_VALUE'1'BOOL_OP;OR;COMPOSITE_TEST;1;TEST @Value(osm_id) = @Value(osm_id)'@Value(Height)'FME_NUM_CONDITIONS2___
    EXTRUDED -> NullAttributeMapper
Note: Remove any rows with null height (invalid buildings)
NullAttributeMapper
    ATTRCHOICE = Selected Attributes
    ATTRLIST = Height
    NEW_VALUE = 15
    NULL_TREATMENT = New Value
    SOURCE_ATTR_VAL = Null
    -> LUCampus (writer CESIUM3DTILES_2)
Note: Save Final output in Cesium 3D Tiles Format
LUCampus (writer CESIUM3DTILES_2)
    attributes: osm_id int, addr:housenumber string, building string, addr:housename string, name string, amenity string, access string, covered string, shop string, power string, operator string, sport string, leisure string, man_made string, residential string, addr:place string, addr:city string, addr:postcode string, bicycle_parking string, building:levels string, wheelchair string, addr:street string, healthcare string, description string, old_name string, website string, fhrs:id string, building:flats string, alt_name string, location string,
      recycling_type string, A int, Unnamed: 0_x int, Property Name string, Property code_x int, Floor int, Space number int, Space Name int, Property code_y string, building_type string, name_x string, Height int, year_of_build int, Total_GIA float
